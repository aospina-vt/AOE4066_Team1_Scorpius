# Missile_Reqs

## RFP - T: Range (Functional)
The missile’s range shall be 500 nm from launch to impact

## RFP - O: Cruise Speed (Functional)
The missile should have a cruise speed of a minimum of Mach 3.

## RFP - T: Mark 41 VLS (Functional)
The missile shall be capable of being launched from land/ship-based Mark 41 VLS

## RFP - O: Land Based Launch (HIMARS) (Functional)
The missile should be capable of being launched from land-based HIMARS and MLRS.

## RFP - O: External Fighter (Functional)
The missile should be capable of being launched from an external fighter carriage.

## RFP - O: Submarine (Functional)
The missile should be capable of being launched from a submarine VLS.

## RFP - O: Internal Fighter (Functional)
The missile should be capable of being launched from an internal fighter carriage.

## RFP - O: Dimensions (Functional)
The missile’s maximum dimensions should be 15 x 15 x 144 in.

## RFP - T: Warhead Size (Functional)
The warhead shall be sized to neutralize a single target

## RFP - O: Data Links (Functional)
The missile should contain Datalink commands to permit in-flight updates.

## RFP - T: Production Run (Functional)
The missile shall have a production run of 1200 missiles per year for 10 years, as well as 100 more for developmental testing

## RFP - T: Surge Production (Functional)
The missile shall have a surge production capability of fabricating 24 units per week to 72 units per week, within a week, to be held indefinitely

## RFP - O: Low-Level Ingress (Functional)
The missile should fly < 500 ft AGL for the last 10% of its mission range.

## RFP - O: Air Launch Conditions (Functional)
The missile should be capable of air launch at Mach 0.85 from 30000 ft.

## MIL-M-8856B: Factor Safety (Functional)
Factor of safety will be a minimum of 1.5 for in-flight, storage, and transportation.

## MIL-M-8856B: Faliure under Ultimate Mission Load (Functional)
The structure will not fail under the ultimate load condition outlined in the mission profile

## MIL-STD-1522A: Extreme Temp (Functional)
Materials will be constructed based on extreme temperature cases seen during the mission profile

## MIL-M-8856B: Heating Effects (Functional)
Missile design shall provide for the cummulative heating effect from internal and external heating

## MIL-M-8856B: Fatigue Life (Functional)
The fatigue life of the structure will equal or exceed the specified life

## SMC-S-006: Proof Pressure (Functional)
Missile shall sustain specified proof pressure without any detrimental deformation

## SMC-S-006: Minimum Proof Pressure (Functional)
Minimum proof pressure will be 1.1 time the maximum expected operating pressure

## SMC-S-006: Stiffness (Functional)
All components will have enough stiffness to handle deformation at limit load

## SMC-S-006: Loading with Cracks (Functional)
Components will handle loads even with existing crack

## SMC-S-006: Fracture Toughness (Functional)
Fracture toughness in materials must be at a minimum of 60% of the plain strain toughness

## SMC-S-006: Fabrication (Functional)
Fabrication of materials will be within acceptable variable ranges and perform reliably

## MIL-STD-1522A: Internal Pressure (Functional)
The system will maintain safe conditions for pressure level inside necessary for flight conditions outlined

## MIL-STD-1901A: Ignition System Protection (Functional)
For safe storage, the ignition system will not arm during exposure to electronic attacks(ie. EMR, ESD,EMP)

## RTCA-DO-178: Software (Functional)
Missile software will comply to military software guidance

## MIL-STD-1760: Connection Interface (Functional)
Missile will be compatible to standard aircraft weapon connection interface

## MIL-STD-704: Electric Power Standard (Functional)
Missile will comply to military electric power standard

## MIL-STD-6016: Data Link System (Functional)
Missile will be compatible to link 16 data link system

## RFP - T: Cost (Functional)
The missile’s unit cost shall not exceed $500,000 (Fiscal Year 24-25).

## MIL-STD-461: Electromagnetic Resistance (Functional)
Missile will be redundant to electromagnetic interference

## RFP - T: Fixed Target Destruction (Functional)
The missile shall neutralize unhardened, fixed surface targets.

## RFP - T: Shelf Life (Functional)
The missile and every physical component shall have a shelf life of at least 10 years without maintenance.

## RFP - T: Entry into Service (Functional)
Design/Development shall commence no later than October 2026 and IOC shall occur no later than December 2031.

## RFP - O: HDBT & Naval Target Destruction (Functional)
The missile should neutralize HDBT and move naval targets.
